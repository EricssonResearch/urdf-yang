module layer2 {
    yang-version 1.1;
    namespace "urn:ietf:params:xml:ns:yang:layer2";
    prefix "l2t";
    
    import robot-network {
        prefix "rnw";
    }

    import ietf-inet-types{
        prefix "inet";
    }

    import robot-network-topology {
        prefix "rnt";
    }
    
    organization
        "HSN-Lab & Ericsson Research Hungary";
    
    contact
        "Editor:    Attila Vidacs";

    description
        "This module defines a model for L2 networking.";

    revision 2023-05-04 {
        description
          "Initial revision.";
        reference
          "RFC 8345: A YANG Data Model for Network Topologies";
    }

    augment "/rnw:networks/rnw:network/rnw:network-types" {
        description
            "Augmentation with L2 topology";
        container l2-topology {
            presence "indicates L2 topology";
            description
                "The presence of the container node indicates L2 topology.";
        }
    }

    augment "/rnw:networks/rnw:network/rnt:link" {
        // when "../rnw:network-types/l2t:l2-topology" {
        // }
        description
          "Augmentation parameters apply only for networks with
           L2 topology";
        list l2-link-attributes {
            description
                "Contains L2 link attributes";
            leaf rate {
                type uint64;
                units "kbps";
                description
                    "Link rate.";
            }
        }
    }

    augment "/rnw:networks/rnw:network/rnw:node/"
         +"rnt:termination-point" {
        // when "../../rnw:network-types/l2t:l2-topology" {
        // }
        description
          "Augmentation parameters apply only for networks with
           L2 topology";
        list l2-termination-point-attributes {
            description
                "Contains termination point L2 attributes";
            leaf name {
                type string;
                description
                    "Name of interface (tp)";
            }
            leaf mac-address{
                type inet:mac-address;
                description
                    "physical address of device";
            }
            leaf bandwidth{
                type uint64;
                units "kbps";
                description
                    "max bandwidth.";
            }
            leaf jitter{
                type uint64;
                units "kbps";
                description
                    "max jitter tolerated.";
            }

        }
    }
}
