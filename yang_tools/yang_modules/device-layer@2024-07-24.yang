module device-layer {
    yang-version 1.1;
    namespace "urn:ietf:params:xml:ns:yang:device-layer";
    prefix "dl";
    
    import ietf-network {
        prefix "nw";
    }

    import ietf-network-topology {
        prefix "nt";
    }

    organization
        "HSN-Lab & Ericsson Research Hungary";

    contact
        "Editor:    Attila Vidacs
        <mailto:vidacs.attila@vik.bme.hu>
        
        Editor:     Marcell Balogh
        <mailto:balogh.marcell@edu.bme.hu>";

    description
        "This module defines a model for device-layer attributes.";

    revision 2024-07-24 {
        description
          "enums updated, aligned with attibute docs";
        reference
          "A YANG Data Model for Device layer in
           Robot Network Topologies";
    }

    revision 2024-06-13 {
        description
          "Initial revision";
        reference
          "A YANG Data Model for Device layer in
           Robot Network Topologies";
    }

    augment "/nw:networks/nw:network" {
        description
            "Device-layer augmentation with a presence attribute.";
        container device-layer-topology {
            leaf element {
                type string;
                description
                    "Attribute to be referenced.";
            }
            presence
                "indicates device-layer topology";
            description
                "The presence of the container node indicates 
                 device-layer topology.";
        }
    }

    augment "/nw:networks/nw:network/nw:node" {
        when "../dl:device-layer-topology" {
        }
        description
          "Contains node (physical device) attributes.";
        container device-layer-node-attributes {
            description
                "Contains node (physical device) attributes.";
            
            leaf device-name {
                type string;
                description
                    "Name of the device.";
            }
            leaf device-type {
                type enumeration{
                    enum pc;
                    enum router;
                    enum switch;
                    enum rpi4;
                    enum modem;
                    enum radiodot;
                    enum flightrack;
                    enum generic;
                    enum robot-arm;
                    enum controlbox;
                    enum camera;
                }
                description
                    "Type of device.";
            }
        }
    }

    augment "/nw:networks/nw:network/nw:node/"
         +"nt:termination-point" {
        when "../../dl:device-layer-topology" {
        }
        description
          "Contains device-layer termination point (physical port) attributes";

        container device-layer-termination-point-attributes {
            description
              "Contains device-layer termination point (physical port) attributes";
            leaf port-name {
                type string;
                description
                  "Name of physical port connector. ";
            }
            leaf port-type {
                type enumeration{
                    enum radio;
                    enum rj45;
                    enum usb-micro;
                    enum usb-a-20;
                    enum usb-a-30;
                    enum usb-c;
                    enum generic;
                }
                description
                  "Format of physical port connector. E.g., RJ45, USB-C";
            }
        }
    }

    augment "/nw:networks/nw:network/nt:link" {
        when "../dl:device-layer-topology" {
        }
        description
          "Contains link (physical device) attributes";
        container device-layer-link-attributes {
            description
                "Contains link attributes.";
            leaf physical-link-name {
                type string;
                description
                    "Name of physical link.";
            }
            leaf physical-link-type {
                type enumeration{
                    enum usb;
                    enum cat5e;
                    enum radio;
                    enum generic;
                }
                description
                    "Type of physical link.";
            }
        }
    }
}
