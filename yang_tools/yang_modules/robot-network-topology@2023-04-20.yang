module robot-network-topology {
    yang-version 1.1;
    namespace "urn:ietf:params:xml:ns:yang:robot-network-topology";
    prefix "rnt";

    import robot-network {
        prefix "rnw";
    }

    organization
        "HSN-Lab & Ericsson Research Hungary";

    contact
        "Editor:    Attila Vidacs";

    description
        "This module defines a common base model for a network topology,
        augmenting the base network data model with links to connect
        nodes, as well as termination points to terminate links
        on nodes.";

    revision 2023-04-20 {
        description
            "Initial revision.";
        reference
            "RFC 8345: A YANG Data Model for Network Topologies";
    }

    typedef link-id {
        type string;
        description
            "An identifier for a link in a topology. -- for example, to indicate the
            type of link and/or the type of topology of which the link is
            a part.";
    }

    typedef tp-id {
        type string;
        description
            "An identifier for termination points on a node. -- for example,
            to indicate the type of termination point and/or the type of
            node that contains the termination point.";
    }

    typedef tf-parent {
        type string;
        description
          "This identifier shows the parent of the object in the
           transformation tree";
    }

    grouping link-ref {
        description
            "This grouping can be used to reference a link in a specific
            network.  Although it is not used in this module, it is
            defined here for the convenience of augmenting modules.";
        leaf link-ref {
            type leafref {
                path "/rnw:networks/rnw:network[rnw:network-id=current()/../"+
                    "network-ref]/rnt:link/nt:link-id";
                require-instance false;
            }
            description
                "A type for an absolute reference to a link instance.
                (This type should not be used for relative references.
                In such a case, a relative path should be used instead.)";
        }
        uses rnw:network-ref;
    }

    grouping tp-ref {
        description
            "This grouping can be used to reference a termination point
            in a specific node.  Although it is not used in this module,
            it is defined here for the convenience of augmenting
            modules.";
        leaf tp-ref {
            type leafref {
                path "/rnw:networks/rnw:network[rnw:network-id=current()/../"+
                    "network-ref]/rnw:node[rnw:node-id=current()/../"+
                    "node-ref]/rnt:termination-point/rnt:tp-id";
                require-instance false;
            }
            description
                "A type for an absolute reference to a termination point.
                (This type should not be used for relative references.
                In such a case, a relative path should be used instead.)";
        }
        uses rnw:node-ref;
    }

    augment "/rnw:networks/rnw:network" {
        description
            "Add links to the network data model.";
        list link {
            key "link-id";
            description
                "A network link connects a local (source) node and
                a remote (destination) node via a set of the respective
                node's termination points.";
            leaf link-id {
                type link-id;
                description
                    "The identifier of a link in the topology.
                    A link is specific to a topology to which it belongs.";
            }
            list source {
                description
                    "This container holds the logical source of a particular
                    link.";
                leaf source-node {
                    type leafref {
                        path "../../../rnw:node/rnw:node-id";
                        // require-instance true;
                        require-instance false;
                    }
                    description
                        "Source node identifier.  Must be in the same topology.";
                }
                leaf source-tp {
                    type leafref {
                        path "../../../rnw:node[rnw:node-id=current()/../"+
                            "source-node]/rnt:termination-point/tp-id";
                        // require-instance true;
                        require-instance false;
                    }
                    description
                        "This termination point is located within the source node
                        and terminates the link.";
                }
            }

            list destination {
                description
                    "This container holds the logical destination of a
                    particular link.";
                leaf dest-node {
                    type leafref {
                        path "../../../rnw:node/rnw:node-id";
                        // require-instance true;
                        require-instance false;
                    }
                    description
                        "Destination node identifier.  Must be in the same
                        network.";
                }
                leaf dest-tp {
                    type leafref {
                        path "../../../rnw:node[rnw:node-id=current()/../"+
                            "dest-node]/rnt:termination-point/tp-id";
                        // require-instance true;
                        require-instance false;
                    }
                    description
                        "This termination point is located within the
                        destination node and terminates the link.";
                }
            }
            list supporting-link {
                key "network-ref link-ref";
                description
                    "Identifies the link or links on which this link depends.";
                leaf network-ref {
                    type leafref {
                        path "../../../rnw:supporting-network/rnw:network-ref";
                    // require-instance true;
                    require-instance false;
                    }
                    description
                        "This leaf identifies in which underlay topology
                        the supporting link is present.";
                }

                leaf link-ref {
                    type leafref {
                        path "/rnw:networks/rnw:network[rnw:network-id=current()/"+
                            "../network-ref]/link/link-id";
                        // require-instance true;
                        require-instance false;
                    }
                    description
                        "This leaf identifies a link that is a part
                        of this link's underlay.  Reference loops in which
                        a link identifies itself as its underlay, either
                        directly or transitively, are not allowed.";
                }
            }
        }
    }

    augment "/rnw:networks/rnw:network"{
        description
            "Augments network with high-level
            control loop parameters that serve as
            a basis of agility score calculation";


        list control-loop {
            key
            "control-loop-id";
            description
            "base control loop parameters";
            leaf control-loop-id {
                type uint32;
                description
                "Identifier for the control loop";
            }
            leaf containing-link-ids {
                type string;
                description
                "Comma-separated list of containing link IDs";
            }
            leaf latency {
                type uint32;
                description
                "Latency requirement for the control loop";
            }
            leaf cycle-time {
                type uint32;
                description
                "Time taken to complete one control loop cycle";
            }
            leaf frequency {
                type uint32;
                description
                "Time taken to complete one control loop cycle";
            }
            leaf accuracy {
                type decimal64{
                    fraction-digits 2;
                }
                description
                "Degree of accuracy required for control loop operations";
            }
            leaf payload-capacity {
                type uint32;
                description
                "Maximum payload capacity for the robot";
            }
            leaf reach {
                type uint32;
                description
                "Maximum reach or operational distance of the robot";
            }
            // leaf safety-features {
            //     type boolean;
            //     description
            //     "Whether the robot includes advanced safety features";
            // }
            leaf safety-features {
                type uint32;
                description
                "Whether the robot includes advanced safety features";
            }

            leaf maintenance-requirements {
                type enumeration {
                    enum "low" {
                        description
                        "Low maintenance requirements";
                    }
                    enum "medium" {
                        description
                        "Medium maintenance requirements";
                    }
                    enum "high" {
                        description
                        "High maintenance requirements";
                    }
                }
                description
                "Level of maintenance required for the robot";
            }

            leaf environment {
                type string;
                description
                "Environmental conditions for the robot (e.g., cleanroom, foundry)";
            }

            leaf safety-standard-compliance {
                type string;
                description
                "Safety standard compliance for the robot";
            }
        }
    }

    augment "/rnw:networks/rnw:network/rnw:node" {
        description
            "Augments termination points that terminate links.
            Termination points can ultimately be mapped to interfaces.";
        list termination-point {
            key "tp-id";
            description
                "A termination point can terminate a link.
                Depending on the type of topology, a termination point
                could, for example, refer to a port or an interface.";
            leaf tp-id {
                type tp-id;
                description
                    "Termination point identifier.";
            }
            list supporting-termination-point {
                key "network-ref node-ref tp-ref";
                description
                    "This list identifies any termination points on which a
                    given termination point depends or onto which it maps.
                    Those termination points will themselves be contained
                    in a supporting node.  This dependency information can be
                    inferred from the dependencies between links.  Therefore,
                    this item is not separately configurable.  Hence, no
                    corresponding constraint needs to be articulated.
                    The corresponding information is simply provided by the
                    implementing system.";

                leaf network-ref {
                    type leafref {
                        path "../../../rnw:supporting-node/rnw:network-ref";
                        // require-instance true;
                        require-instance false;
                    }
                    description
                        "This leaf identifies in which topology the
                        supporting termination point is present.";
                }
                leaf node-ref {
                    type leafref {
                        path "../../../rnw:supporting-node/rnw:node-ref";
                    // require-instance true;
                    require-instance false;
                    }
                    description
                        "This leaf identifies in which node the supporting
                        termination point is present.";
                }
                leaf tp-ref {
                    type leafref {
                        path "/rnw:networks/rnw:network[rnw:network-id=current()/"+
                            "../network-ref]/rnw:node[rnw:node-id=current()/../"+
                            "node-ref]/rnt:termination-point/tp-id";
                        // require-instance true;
                        require-instance false;
                    }
                    description
                        "Reference to the underlay node (the underlay node must
                        be in a different topology).";
                }
            }
        }
    }
}
