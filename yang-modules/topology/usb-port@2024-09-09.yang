module usb-port {
  yang-version 1.1;
  namespace "urn:ietf:params:xml:ns:yang:usb-port";
  prefix usb;

  import ietf-network {
    prefix nw;
  }

  import ietf-network-topology {
    prefix nt;
  }

  import device-layer {
    prefix dl;
  }

  organization
    "HSN-Lab & Ericsson Research Hungary";

  contact
    "Editor:     Marcell Balogh
    <mailto:balogh.marcell@edu.bme.hu>";

  description
    "This module defines a generic USB port with default values.";

  revision 2024-09-09 {
    description "Initial revision.";
  }

  augment "/nw:networks/nw:network/nw:node/nt:termination-point/dl:device-layer-termination-point-attributes"{
    when "/nw:networks/nw:network/nw:node/nt:termination-point/dl:device-layer-termination-point-attributes/dl:port-type = 'usb'"  {
    }

    leaf version {
      type string;
      description "Version of the USB port (e.g., USB2.0, USB3.0).";
    }

    leaf power-consumption {
      type decimal64 {
        fraction-digits 2;
      }
      units "W";
      default "2.5";  // Default power consumption for USB2.0 in watts
      description "Power consumption of the port.";
    }
  }

  augment "/nw:networks/nw:network/nt:link/dl:device-layer-link-attributes"{
    when "/nw:networks/nw:network/nw:node/nt:termination-point/dl:device-layer-termination-point-attributes/dl:port-type = 'usb'"  {
    }

    leaf source-connector-type {
        type string;
        description
            "Source connector type (e.g., usb20, usb30).";
    }
    leaf destination-connector-type {
        type string;
        description
            "Destination connector type (e.g., usb20, usb30).";
    }
    leaf max-data-transfer {
        type uint16;
        units "Gbps";
        description
            "maximum data transfer rate in Gbps";
    }
    leaf max-power-transfer {
        type uint16;
        units "W";
        description
            "maximum power transfer in W";
    }
  }
}
