module usb3-port {
  yang-version 1.1;
  namespace "urn:ietf:params:xml:ns:yang:usb3-port";
  prefix "usb3";

  import usb-port {
    prefix "usb";
  }

  organization
    "HSN-Lab & Ericsson Research Hungary";

  contact
    "Editor:     Marcell Balogh
    <mailto:balogh.marcell@edu.bme.hu>";

  description
    "This module augments the generic USB port with USB3.0-specific parameters.";

  revision 2024-09-09 {
    description "Initial revision.";
  }

  augment "/usb:usb-port" {
    when "usb:version = 'USB3.0'";
    description "USB3.0-specific attributes";

    leaf max-current {
      type uint16;
      units "mA";
      default "900";  // Default max current for USB3.0 in mA
      description "Maximum current for USB3.0 port.";
    }

    leaf signaling-rate {
      type decimal64 {
        fraction-digits 2;
      }
      units "Gbps";
      default "5000";  // Default signaling rate for USB3.0 in Gbps
      description "Signaling rate of USB3.0.";
    }

    leaf backward-compatible {
      type boolean;
      default "true";  // Default: USB3.0 is backward compatible with USB2.0
      description "Indicates if USB3.0 is backward compatible with USB2.0.";
    }
  }
}
