//minden modellezheto closed-loop controlkent.
//az open loop control az nem a closed loop control specialis esete, ezert az kulon van de amugy igen?

module my-control-system {
  namespace "urn:control-system";
  prefix "cs";

  import ietf-inet-types {
    prefix "inet";
  }

  // Data nodes
  container control-system-data {
    description "Data nodes for the control system.";

    leaf setpoint {
      type int32;
      description "The desired setpoint.";
    }

    leaf current-value {
      type int32;
      description "Current value being controlled.";
    }
  }

  // RPC operation
  rpc control-operation {
    description "Perform a control operation.";

    input {
      leaf target-value {
        type int32;
        description "The value to set the system to.";
      }
    }

    output {
      leaf success {
        type boolean;
        description "Operation success status.";
      }
    }
  }

  // Notification
  notification control-status-change {
    description "Notification for control system status change.";

    leaf new-value {
      type int32;
      description "The new value after a control operation.";
    }
  }
}


//masik node-ba:
//A feature node allows you to define optional features in your YANG module. Features can be used to enable or disable certain parts of your module's schema based on conditions.

feature advanced-control {
  description "Enable advanced control features.";
}

//An action node allows you to define a custom action or operation within your YANG module. Actions are not RPCs but are often used for more specific, custom operations. Here's an example:
action reset-system {
  description "Reset the control system to its default state.";
  input {
    leaf reset-type {
      type enumeration {
        enum hard-reset;
        enum soft-reset;
      }
      description "Type of reset operation.";
    }
  }
}
