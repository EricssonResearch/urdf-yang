module container {
    yang-version 1.1;
    namespace "urn:container";
    prefix "cnt";
    
    import network {
        prefix "nw";
    }

    import network-topology {
        prefix "nt";
    }

    contact
        "Editor:    Attila Vidacs";

    description
        "This module defines a model for (Docker) container networking.";

    revision 2023-05-04;


    augment "/nw:networks/nw:network/nw:network-types" {
        container container-networking {
            presence "indicates container networking";
            description
                "The presence of the container node indicates container networking level.";
        }
    }

    augment "/nw:networks/nw:network" {
        when "nw:network-types/cnt:container-networking" {
            description
                "Augmentation parameters apply only for container networking.";
        }
        container container-networks-list {
            description 
                "Networks that service containers are attached to.";
            list network {
                key "network-id";
                leaf network-id {
                    type string;
                    description
                        "Identifies a container network.";
                }
            }
        }
    }

    augment "/nw:networks/nw:network/nw:node" {
        when "../nw:network-types/cnt:container-networking" {
        description
            "Augmentation parameters apply only for networks with
            container-networking-type";
        }
        container container-node-attributes {
            description
                "Contains container node attributes";
            leaf image {
                type string;
                description
                    "Specifies the image to start the container from. E.g., ros:noetic-ros-core";
            }
            list networks {
                key "network-ref";
                leaf network-ref {
                    type leafref {
                        path "/nw:networks/nw:network/nw:network-id";
                    require-instance false;
                    }
                }
            }
            container host {
                leaf network-ref {
                    type leafref {
                        path "/nw:networks/nw:network/nw:network-id";
                    require-instance true;
                    }
                }
                leaf node-ref {
                    type leafref {
                        path "/nw:networks/nw:network/nw:node/nw:node-id";
                        require-instance true;
                    }
                }
            }
        }
    }
}
