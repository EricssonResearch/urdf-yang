module layer1 {
    yang-version 1.1;
    namespace "urn:layer1";
    prefix "l1t";
    
    import network {
        prefix "nw";
    }

    import network-topology {
        prefix "nt";
    }

    contact
        "Editor:    Attila Vidacs";

    description
        "This module defines a model for L1 (physical) networking.";

    revision 2023-04-26;

    typedef device-type {
        description "Device types";
        type enumeration {
            enum router;
            enum pc;
            enum robotic-arm;
            enum gripper;
            enum switch;
            enum other;
            enum camera;
            enum rpi4;
            enum 5g-modem;
        }
    }

    typedef link-type {
        description "Device types";
        type enumeration {
            enum wired;
            enum wireless;
        }
    }


    augment "/nw:networks/nw:network/nw:network-types" {
        container l1-topology {
            presence "Indicates L1 topology";
            description
                "The presence of the container node indicates L1 topology";
        }
    }

    augment "/nw:networks/nw:network/nw:node" {
        when "../nw:network-types/l1t:l1-topology" {
        description
            "Augmentation parameters apply only for networks with
            L1 topology";
        }
        container l1-node-attributes {
            description
                "Contains node (physical device) attributes";
            leaf device-type {
                type device-type;
                description
                    "Type of device. E.g., robot-arm, switch, rpi4, ...";
            }
        }
    }

    augment "/nw:networks/nw:network/nt:link" {
        when "../nw:network-types/l1t:l1-topology" {
            description
                "Augmentation parameters apply only for networks with
                L1 topology";
        }
        container l1-link-attributes {
            description
                "Contains link attributes.";
            leaf type {
                type link-type;
                description
                    "Link type. E.g., wired, wireless";
            }
        }
    }

    augment "/nw:networks/nw:network/nw:node/"
         +"nt:termination-point" {
        when "../../nw:network-types/l1t:l1-topology" {
            description
                "Augmentation parameters apply only for networks with
                L1 topology";
        }
        container l1-termination-point-attributes {
            description
                "Contains L1 termination point (physical port) attributes";
            leaf connector-type {
                type string;
                description
                    "Type of physical port connector. E.g., RJ45, USB-C";
            }
        }
    }
}
