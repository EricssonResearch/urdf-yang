module robot-network {
    yang-version 1.1;
    namespace "urn:robot-network";
    prefix "nw";

    revision 2023-04-20 {
        description
            "Initial revision.";
        reference
            "RFC 8345: A YANG Data Model for Network Topologies";
    }

    typedef node-id {
        type string;
        description
            "Identifier for a node. -- for example, to indicate the type of node.";
    }

    typedef network-id {
        type string;
        description
            "Identifier for a network.  -- for example,
            to indicate the type of network.";
    }

    grouping network-ref {
        description
            "Contains the information necessary to reference a network --
            for example, an underlay network.";
        leaf network-ref {
            type leafref {
                path "/nw:networks/nw:network/nw:network-id";
                require-instance false;
            }
            description
                "Used to reference a network -- for example, an underlay
                network.";
        }
    }

    grouping node-ref {
        description
            "Contains the information necessary to reference a node.";
        leaf node-ref {
            type leafref {
                path "/nw:networks/nw:network[nw:network-id=current()/../"+
                "network-ref]/nw:node/nw:node-id";
                require-instance false;
            }
            description
                "Used to reference a node.
                Nodes are identified relative to the network that
                contains them.";
        }
        uses network-ref;
    }

    container networks {
        description "Robot System";
        list network {
            key "network-id";
            description
                "Describes a network.
                A network typically contains an inventory of nodes,
                topological information (augmented through the
                network-topology data model), and layering information.";
            leaf network-id {
                type network-id;
                description
                    "Identifies a network.";
            }
            container network-types {
                description
                "Serves as an augmentation target.
                The network type is indicated through corresponding
                presence containers augmented into this container.";
            }
            list supporting-network {
                key "network-ref";
                description
                    "An underlay network, used to represent layered network
                    topologies.";
                leaf network-ref {
                    type leafref {
                        path "/nw:networks/nw:network/nw:network-id";
                    require-instance false;
                }
                    description
                        "References the underlay network.";
                }
            }

            list node {
                key "node-id";
                description
                    "The inventory of nodes of this network.";
                leaf node-id {
                    type node-id;
                    description
                        "Uniquely identifies a node within the containing
                        network.";
                }
                list supporting-node {
                    key "network-ref node-ref";
                    description
                        "Represents another node that is in an underlay network
                        and that supports this node.  Used to represent layering
                        structure.";
                    leaf network-ref {
                        type leafref {
                            path "../../../nw:supporting-network/nw:network-ref";
                        require-instance false;
                        }
                        description
                        "References the underlay network of which the
                        underlay node is a part.";
                    }
                    leaf node-ref {
                        type leafref {
                            path "/nw:networks/nw:network/nw:node/nw:node-id";
                            require-instance false;
                        }
                        description
                            "References the underlay node itself.";
                    }
                }
            }
        }
    }
}
