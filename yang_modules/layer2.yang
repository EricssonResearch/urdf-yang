module layer2 {
    yang-version 1.1;
    namespace "urn:layer2";
    prefix "l2t";
    
    import network {
        prefix "nw";
    }

    import network-topology {
        prefix "nt";
    }

    contact
        "Editor:    Attila Vidacs";

    description
        "This module defines a model for L2 networking.";

    revision 2023-05-04;


    augment "/nw:networks/nw:network/nw:network-types" {
        container l2-topology {
            presence "indicates L2 topology";
            description
                "The presence of the container node indicates L2 topology.";
        }
    }

    augment "/nw:networks/nw:network/nt:link" {
        when "../nw:network-types/l2t:l2-topology" {
            description
                "Augmentation parameters apply only for networks with
                L2 topology";
        }
        container l2-link-attributes {
            description
                "Contains L2 link attributes";
            leaf rate {
                type uint64;
                units "kbps";
                description
                    "Link rate.";
            }
        }
    }

    augment "/nw:networks/nw:network/nw:node/"
         +"nt:termination-point" {
        when "../../nw:network-types/l2t:l2-topology" {
            description
                "Augmentation parameters apply only for networks with
                L2 topology";
        }
        container l2-termination-point-attributes {
            description
                "Contains termination point L2 attributes";
            leaf name {
                type string;
                description
                    "Name of interface (tp)";
            }
            leaf mac-address {
                type string;
                description
                    "Interface MAC address.";
            }
        }
    }
}
